-- *****************************************************************
-- BDCOM-FILTER-TRAP.my: BDCOM FILTER TRAP MIB
--
-- November 2008
-- Edit by LIUQIANG
-- Copyright (c) 2008 by BDCOM, Inc.
-- All rights reserved.
-- *****************************************************************

BDCOM-FILTER-TRAP DEFINITIONS ::= BEGIN




IMPORTS
    MODULE-IDENTITY, OBJECT-TYPE, NOTIFICATION-TYPE,INTEGER,
    Integer32, Unsigned32                       FROM SNMPv2-SMI
    MODULE-COMPLIANCE, OBJECT-GROUP,
    NOTIFICATION-GROUP                          FROM SNMPv2-CONF
    bdlocal                              		FROM BDCOM-SMI
    IpAddress, TimeTicks                                   FROM RFC1155-SMI
    PhysAddress				                FROM RFC1213-MIB;

--definition of the filter table content

               bdfilter         OBJECT IDENTIFIER ::= { bdlocal 222 }
               
               TypeOfBlock ::= INTEGER
                	{ arp(1),
                           bpdu(2),
                           dhcp(3),
                           ip(4),
                           igmp(5)
                         }
                         
               TypeOfAction ::= INTEGER
                         {
                           off(0),
                           on(1)
                          }

               
               
               
               bdFilterTable OBJECT-TYPE
                   SYNTAX  SEQUENCE OF BDCOMFilterEntry
                   ACCESS  not-accessible
                   STATUS  mandatory
                   DESCRIPTION
                            "A list of filter entries."
                   ::= { bdfilter 1 }

               bdFilterEntry OBJECT-TYPE
                   SYNTAX  BDCOMFilterEntry
                   ACCESS  not-accessible
                   STATUS  mandatory
                   DESCRIPTION
                            "A collection of filter objects in the
                            BDCOM device which includes the blocked content."
                   INDEX { filterIndex }
               ::= { bdFilterTable 1 }

               BDCOMFilterEntry ::=
                   SEQUENCE {
                       lineIndex
                           INTEGER (0..32),
                       timeOcr
                           TimeTicks,
                       timeHold
                           TimeTicks,                       
                       filterIpAddress    
                           IpAddress,
                       filterPhyAddress
                       	   PhysAddress,
                       portNum
                       	   INTEGER,
                       message
                       	   TypeOfBlock,
                       vlanID
                       	   INTEGER (1..4094),
                       Action
                       	   TypeOfAction	
                  }
              
		
               lineIndex OBJECT-TYPE
                   SYNTAX  INTEGER (0..32)
                   ACCESS  read-only
                   STATUS  mandatory
                   DESCRIPTION
                           "index of the filter table."
                   ::= { bdFilterEntry 1 }
		

              timeOcr OBJECT-TYPE
                   SYNTAX  TimeTicks
              	   ACCESS  read-only
              	   STATUS  mandatory
              	   DESCRIPTION
                   	   "Occurance time of blocking."
              	   ::= { bdFilterEntry 2 }



              timeHold OBJECT-TYPE
                   SYNTAX  TimeTicks
              	   ACCESS  read-only
              	   STATUS  mandatory
              	   DESCRIPTION
                   	   "Hold time of blocking."
              	   ::= { bdFilterEntry 3 }


              filterIpAddress OBJECT-TYPE
                   SYNTAX  IpAddress
                   ACCESS  read-only
                   STATUS  mandatory
                    DESCRIPTION
                      "The IP address of blocked device."
              	   ::= { bdFilterEntry 4 }


              filterPhyAddress OBJECT-TYPE
                   SYNTAX  PhysAddress
              	   ACCESS  read-only
              	   STATUS  mandatory
              	   DESCRIPTION
                   	   "The mac address of blocked device."
              	   ::= { bdFilterEntry 5 }

              portNum OBJECT-TYPE
                   SYNTAX  INTEGER
                   ACCESS  read-only
                   STATUS  mandatory
                   DESCRIPTION
                           "interface index to be blocked."
                   ::= { bdFilterEntry 6 }

              message OBJECT-TYPE
                   SYNTAX  TypeOfBlock
              	   ACCESS  read-only
              	   STATUS  mandatory
              	   DESCRIPTION
                   	   "Type of blocking."
              	   ::= { bdFilterEntry 7 }


              vlanID OBJECT-TYPE
                   SYNTAX  INTEGER (1..4094)
                   ACCESS  read-only
                   STATUS  mandatory
                    DESCRIPTION
                      "The vlan identifier of blocked device port."
              	   ::= { bdFilterEntry 8 }


              Action OBJECT-TYPE
                   SYNTAX  TypeOfAction
              	   ACCESS  read-only
              	   STATUS  mandatory
              	   DESCRIPTION
                   	   "The action, which means block or unblock."
              	   ::= { bdFilterEntry 9 }
                   

-- Notifications
	bdFilterMIBNotifications OBJECT IDENTIFIER
                                ::= { bdfilter 2 }


	bdFilterNotification NOTIFICATION-TYPE
    		OBJECTS {
                       timeOcr,
                       timeHold,
                       filterIpAddress,
                       filterPhyAddress,
                       portNum,
                       message,
                       vlanID,
                       Action
    		}
    		STATUS      current
    		DESCRIPTION
        	"The agent generates this notification when certain defined types of packages have been blocked or unblocked."
    		::= { bdFilterMIBNotifications 1 }

              

END
