--------------------------------------------------------------------
-- BDCOM-CHASSIS
-- Jun 2000
--------------------------------------------------------------------

            BDCOM-CHASSIS DEFINITIONS ::= BEGIN

            IMPORTS
                    TimeTicks
            FROM RFC1155-SMI
                    OBJECT-TYPE
			FROM RFC-1212
                    DisplayString
			FROM RFC1213-MIB
		    bdtemporary
			FROM BDCOM-SMI;
          
               bdchassis             OBJECT IDENTIFIER ::= { bdtemporary 6 }

   
               bdchassisType OBJECT-TYPE
                   SYNTAX  INTEGER {
                        unknown(0),
                        bd2003(1),
                        bd5010(2),
                        bd2750(3),
                        bd3720(4),
                        bdv100(5),
			bdv200(6),
			bdv300(7),
			bd1750(8),
			bd1760(9),
			bd2650(10),
			bd2651(11),
			bd3660(12),
			bd3680(13),
			bd2630(14),
			bd2621(15),
			bd1720(16),
			bd2640(17),
			bd1721(18),
			bds3224(101),
			bds3224m(102),
			bds2226(103), 
			bds2224(104),
			bds2248(105),
			bds2026(106),
			bds2224m(107),
			bds3512(108),
			bds6508(109)
                   }
                   ACCESS  read-only
                   STATUS  mandatory
                   DESCRIPTION
                           "Chassis type."
                   ::= { bdchassis 1 }

               bdchassisVersion OBJECT-TYPE
                   SYNTAX  DisplayString
                   ACCESS  read-only
                   STATUS  mandatory
                   DESCRIPTION
                           "Chassis hardware revision level, or an empty
                           string if unavailable."
                   ::= { bdchassis 2 }

               bdchassisId OBJECT-TYPE
                   SYNTAX  DisplayString
                   ACCESS  read-write
                   STATUS  mandatory
                   DESCRIPTION
                           "Unique ID string. Defaults to chassis serial
                           number if available, otherwise empty."
                   ::= { bdchassis 3 }

               bdromSysVersion OBJECT-TYPE
                   SYNTAX  DisplayString
                   ACCESS  read-only
                   STATUS  mandatory
                   DESCRIPTION
                           "ROM system software version, or an empty
                           string if unavailable."
                   ::= { bdchassis 4 }

               bdprocessorRam OBJECT-TYPE
                   SYNTAX  INTEGER
                   ACCESS  read-only
                   STATUS  mandatory
                   DESCRIPTION
                           "Bytes of RAM available to CPU."
                   ::= { bdchassis 5 }

               bdnvRAMSize OBJECT-TYPE
                   SYNTAX  INTEGER
                   ACCESS  read-only
                   STATUS  mandatory
                   DESCRIPTION
                           "Bytes of non-volatile configuration memory."
                   ::= { bdchassis 6 }

               bdnvRAMUsed OBJECT-TYPE
                   SYNTAX  INTEGER
                   ACCESS  read-only
                   STATUS  mandatory
                   DESCRIPTION
                           "Bytes of non-volatile configuration memory
                           in use."
                   ::= { bdchassis 7 }

               bdconfigRegister OBJECT-TYPE
                   SYNTAX  INTEGER
                   ACCESS  read-only
                   STATUS  mandatory
                   DESCRIPTION
                           "Value of configuration register."
                   ::= { bdchassis 8 }

               bdconfigRegNext OBJECT-TYPE
                   SYNTAX  INTEGER
                   ACCESS  read-only
                   STATUS  mandatory
                   DESCRIPTION
                           "Value of configuration register at next
                           reload."
                   ::= { bdchassis 9 }

               bdcardTable OBJECT-TYPE
                   SYNTAX  SEQUENCE OF BdCardTableEntry
                   ACCESS  not-accessible
                   STATUS  mandatory
                   DESCRIPTION
                            "Chassis card table."
                   ::= { bdchassis 10 }

               bdcardTableEntry OBJECT-TYPE
                   SYNTAX BdCardTableEntry
                   ACCESS  not-accessible
                   STATUS  mandatory
                   DESCRIPTION
                            "Chassis card table."
                   INDEX { bdcardIndex }
               ::= { bdcardTable 1 }

               BdCardTableEntry ::=
                   SEQUENCE {
                       bdcardIndex
                           INTEGER,
                       bdcardType
                           INTEGER,
                       bdcardDescr
                           DisplayString,
                       bdcardSerial
                           DisplayString,
                       bdcardHwVersion
                           DisplayString,
                       bdcardSwVersion
                           DisplayString,
                       bdcardSlotNumber
                           INTEGER,
                       bdcardContainedByIndex
                           INTEGER,
                       bdcardOperStatus
                           INTEGER,
                       bdcardSlots
                           INTEGER
                   }


          -- The following section describes the components of the
          -- table.

               bdcardIndex OBJECT-TYPE
                   SYNTAX  INTEGER
                   ACCESS  read-only
                   STATUS  mandatory
                   DESCRIPTION
                           "Index into cardTable (not physical chassis
                           slot number)."
                   ::= { bdcardTableEntry 1 }

               bdcardType OBJECT-TYPE
                   SYNTAX  INTEGER {
						unknown(0),
						scc-serial(1),
						ethernet-10M(2),
						scc-pri-e1(3),
						scc-bri(4),
						scc-data-encription(5),
						vc2-fxsa(6),
						vc2-fxso(7),
						scc-mcard-3port(8),
						scc-mcard-2port(9),
						pci-4asyn-syn(10),
						pci-8asyn-syn(11),
						pci-8asyn(12),
						pci-16asyn(13),
						pci-1e1-pri(14),
						pci-4e1-pri(15),
						pci-1bri(16),
						pci-4bri(17),
						pci-1atm-155m(18),
						pci-data-encription(19),
						pci-vc4-fxsa(20),
						pci-vc4-fxoa(21),
						pci-vc2-ema(22),
						pci-ethernet-100m(23),
						pci-mcard-4port(24),
						vc2-dsp(25),
						scc-mcard-1750-2slot(26),
						scc-mcard-1760-3slot(27),
						pci-mcard-2650-5slot(28),
						pci-mcard-2651-5slot(29),
						pci-mcard-3660-6slot(30),
						pci-mcard-3680-8slot(31),
						scc-two-ethernet-card(32),
						scc-two-serial-card(33),
						scc-eth-ser-card(34),
						scc-T1-card(35),
						scc-mcard-2630-2slot(36),
						scc-mcard-2621-2slot(37),
						scc-mcard-1720-2slot(38),
						pci-mcard-2640-4slot(39),
						scc-1modem(40),
						pci-6modem(41),
						pci-12modem(42),
						pci-4BRI(43),
						pci-1T1E1B(44),
						pci-2T1E(45),
						pci-2T1B(46),
						scc-x21-1serial(47),
						scc-x21-2serial(48),
						pci-2e1-pri(49),
						scc-1Isdn-lease(50),
						scc-1dtu(51),
						fcc-Ethernet-100M(52),
						scc-8async-card(53),
						pci-2ethernet-100M(54),
						pci-vc4-EM(55),
						pci-vc4-FXSO(56),
						scc-mcard-1721-3slot(57),
						pci-4UE1(60), 		--PCI 4 port Unframed E1 card 	
						
						pci-mcard-s3224-2slot(201),
						pci-mcard-s3224m-6slot(202),
						pci-mcard-s2226-2slot(203),
						pci-mcard-s2224-2slot(204),
						pci-mcard-s2248-2slot(205),
						pci-mcard-s2026-2slot(206),
						pci-mcard-s2224m-6slot(207),
						pci-mcard-s3512-3slot(208),
						pci-mcard-s6506-8slot(209),
						pci-mcard-s2116-1slot(210),
						pci-mcard-s3448-4slot(211),
						pci-mcard-s2108-1slot(212),
						pci-mcard-s2008-0slot(213),
						pci-mcard-s6508-10slot(214),

						pci-48FastEthernet-100M(251),
						pci-32FastEthernet-100M(252),
						pci-24FastEthernet-100M(253),
						pci-16FastEthernet-100M(254),
						pci-8FastEthernet-100M(255),
						pci-4FastEthernet-100M(256),
						pci_1FastEthernet-100M(257),
						pci_1GigaEthernet-100M(258),
						pci_1FastEthernet-1000M(259),
						pci_1GigaEthernet-1000M(260),
						pci_1GBIC(261),
						pci_1STACK(262),
						pci_8Fiber(263),
						pci_4GigaEthernet-Combo-1000M(264),
						pci_4GigaEthernet-SFP-1000M(265),
						pci_6508-MSU(266),
						pci_2GigaEthernet-SFP-1000M(267),
						pci_2GigaEthernet-1000M(268)
					}
                   ACCESS  read-only
                   STATUS  mandatory
                   DESCRIPTION
                           "Functional type of this card."
                   ::= { bdcardTableEntry 2 }

               bdcardDescr OBJECT-TYPE
                   SYNTAX  DisplayString
                   ACCESS  read-only
                   STATUS  mandatory
                   DESCRIPTION
                           "Text description of this card."
                   ::= { bdcardTableEntry 3 }

               bdcardSerial OBJECT-TYPE
                   SYNTAX  DisplayString
                   ACCESS  read-only
                   STATUS  mandatory
                   DESCRIPTION
                           "The serial number of this card, or 0 if unavailable."
                   ::= { bdcardTableEntry 4 }

               bdcardHwVersion OBJECT-TYPE
                   SYNTAX  DisplayString
                   ACCESS  read-only
                   STATUS  mandatory
                   DESCRIPTION
                           "Hardware revision level of this card, or an
                           empty string if unavailable."
                   ::= { bdcardTableEntry 5 }

               bdcardSwVersion OBJECT-TYPE
                   SYNTAX  DisplayString
                   ACCESS  read-only
                   STATUS  mandatory
                   DESCRIPTION
                           "Version of the firmware or microcode
                           installed on this card, or an empty string if
                           unavailable."
                   ::= { bdcardTableEntry 6 }

               bdcardSlotNumber OBJECT-TYPE
                   SYNTAX  INTEGER
                   ACCESS  read-only
                   STATUS  mandatory
                   DESCRIPTION
                           "Slot number relative to the containing card or 
                           chassis, or -1 if neither applicable nor 
                           determinable."
                   ::= { bdcardTableEntry 7 }

               bdcardContainedByIndex OBJECT-TYPE
                   SYNTAX  INTEGER
                   ACCESS  read-only
                   STATUS  mandatory
                   DESCRIPTION
                           "cardIndex of the parent card which
                           directly contains this card, or 0 if
                           contained by the chassis, or -1 if not
                           applicable nor determinable."
                   ::= { bdcardTableEntry 8 }

               bdcardOperStatus OBJECT-TYPE
                   SYNTAX  INTEGER {
                          not-specified(1), 
                          up(2),
                          down(3),
                          standby(4)
                      }
                   ACCESS  read-only
                   STATUS  mandatory
                   DESCRIPTION
                           "The operational status of the card.
                           bdcardOperStatus is up when a card is
                           recognized by the device and is enabled for
                           operation. bdcardOperStatus is down if the
                           card is not recognized by the device, or if
                           it is not enabled for operation.
                           bdcardOperStatus is standby if the card is
                           enabled and acting as a standby slave"
                   ::= { bdcardTableEntry 9 }

               bdcardSlots OBJECT-TYPE
                   SYNTAX  INTEGER
                   ACCESS  read-only
                   STATUS  mandatory
                   DESCRIPTION
                           "Number of slots on this card, or 0 if no
                           slots or not applicable, or -1 if not 
			   determinable."
                   ::= { bdcardTableEntry 10 }

               -- End of table


               bdchassisSlots OBJECT-TYPE
                   SYNTAX  INTEGER
                   ACCESS  read-only
                   STATUS  mandatory
                   DESCRIPTION
                           "Number of slots in this chassis, or -1 of
                           neither applicable nor determinable."
                   ::= { bdchassis 11 }

               bdcardIfIndexTable OBJECT-TYPE
                   SYNTAX  SEQUENCE OF BdCardIfIndexEntry
                   ACCESS  not-accessible
                   STATUS  mandatory
                   DESCRIPTION
                            "Chassis card table."
                   ::= { bdchassis 12 }

               bdcardIfIndexEntry OBJECT-TYPE
                   SYNTAX BdCardIfIndexEntry
                   ACCESS  not-accessible
                   STATUS  mandatory
                   DESCRIPTION
                            "Chassis card table."
                   INDEX { bdcardIfIndex }
               ::= { bdcardIfIndexTable 1 }

               BdCardIfIndexEntry ::=
                   SEQUENCE {
                       bdcardIfIndex
                           INTEGER,
                       bdcardIfPortNumber
                           INTEGER,
                       bdcardIfCardIndex
                           INTEGER,
                       bdcardIfConnectorTypeEnabled
                           INTEGER
                   }

               bdcardIfIndex OBJECT-TYPE
                   SYNTAX  INTEGER
                   ACCESS  read-only
                   STATUS  mandatory
                   DESCRIPTION
                           "matches RFC1213/RFC2233 ifTable IfIndex"
                   ::= { bdcardIfIndexEntry 1 }
                   
               bdcardIfPortNumber OBJECT-TYPE
                   SYNTAX  INTEGER
                   ACCESS  read-only
                   STATUS  mandatory
                   DESCRIPTION
                           "Chassis port number, unique per port on a 
                            given card if available."
                   ::= { bdcardIfIndexEntry 2 }

               bdcardIfCardIndex OBJECT-TYPE
                   SYNTAX  INTEGER
                   ACCESS  read-only
                   STATUS  mandatory
                   DESCRIPTION
                           "bdcardIndex of the card in the Chassis 
			   				bdcardTable which contains this interface."
                   ::= { bdcardIfIndexEntry 3 }

               bdcardIfConnectorTypeEnabled OBJECT-TYPE
                   SYNTAX  INTEGER {
                           not-specified(1), 
                           none(2),
                           rj-11(3),
                           rj-45(4),
                           db-15(5), 
                           db-44(6),
                           db-60(7)                         
                   }
                   ACCESS  read-only
                   STATUS  mandatory
                   DESCRIPTION
                           "Interface connector type currently
                           enabled. Value will be 1 if not known or not
                           used, or 2 if none of this ports' interface
                           connectors are enabled."
                   ::= { bdcardIfIndexEntry 4 }

	       -- End of table

               bdsysUpTimeAtLastChassisChange OBJECT-TYPE
                   SYNTAX  TimeTicks
                   ACCESS  read-only
                   STATUS  mandatory
                   DESCRIPTION
                           "Time in seconds100 from the last cold
                           start to the last change in the chassis
                           configuration. This value will be updated
                           whenever the chassis experiences a change
                           in the count, type, or slot position of
                           a card in cardTable."
                   ::= { bdchassis 13 }

                bdBoxTemp   OBJECT-TYPE
                    SYNTAX		INTEGER (1..100)
                    MAX-ACCESS	read-only
                    STATUS		current
                    DESCRIPTION
                        "The environment temperature in the mechine box."
                    ::= { bdchassis 14 }

                bdAuxTable OBJECT-TYPE
                    SYNTAX		SEQUENCE OF bdAuxEntry
                    MAX-ACCESS	not-accessible
                    STATUS		current
                    DESCRIPTION
                        "A list of Auxiliary devices status entries."
                    ::= { bdchassis 15 }

                bdAuxEntry               OBJECT-TYPE
                    SYNTAX		bdAuxEntry 
                    MAX-ACCESS	not-accessible
                    STATUS		current
                    DESCRIPTION
                        "An entry of auxiliary devices status table."
                    INDEX	{ bdAuxIndex }
                    ::= { bdAuxTable 1 }

                bdAuxEntry ::=
                    SEQUENCE {
                        bdAuxIndex   Gauge32,
                        bdAuxClass   INTEGER,
                        bdAuxDescr   DisplayString,
                        bdAuxMode    INTEGER,
                        bdAuxState   INTEGER
                    }

                bdAuxIndex   OBJECT-TYPE
                    SYNTAX		Gauge32 
                    MAX-ACCESS	read-only
                    STATUS		current
                    DESCRIPTION
                        "The index of Aux status table."
                    ::= {  bdAuxEntry 1 }

                bdAuxDescr  OBJECT-TYPE
                    SYNTAX		DisplayString
                    MAX-ACCESS	read-only
                    STATUS		current
                    DESCRIPTION
                        " The description of  an auxiliary device. "
                    ::= {  bdAuxEntry 2}

                bdAuxClass   OBJECT-TYPE
                    SYNTAX		INTEGER{power(1),fan(2)} 
                    MAX-ACCESS	read-only
                    STATUS		current
                    DESCRIPTION
                        "Auxiliary device,such as power supply ,fan..."
                    ::= {  bdAuxEntry 3 }

                bdAuxMode  OBJECT-TYPE
                    SYNTAX		INTEGER{ active(1),backup(2),loadshare(3)}
                    MAX-ACCESS	read-only
                    STATUS		current
                    DESCRIPTION
                        "The working mode of  an auxiliary device."
                    ::= {  bdAuxEntry 4}

                bdAuxState  OBJECT-TYPE
                    SYNTAX		INTEGER{ ok(1),failure(2)}
                    MAX-ACCESS	read-only
                    STATUS		current
                    DESCRIPTION
                        "The state of  an auxiliary device."
                    ::= {  bdAuxEntry 5}
                END
