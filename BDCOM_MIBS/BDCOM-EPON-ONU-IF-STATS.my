-- *****************************************************************
-- BDCOM-EPON-ONU-IF-STATS.MIB:  BDCom LLID ONU MIB file
-- AUG 2009
-- *****************************************************************
--

               BDCOM-EPON-ONU-IF-STATS DEFINITIONS ::= BEGIN

               IMPORTS
                    Counter, IpAddress, Counter
			FROM RFC1155-SMI
		    OBJECT-TYPE
			FROM RFC-1212
                    DisplayString
			FROM RFC1213-MIB
		    bdEponOnuIf
			FROM BDCOM-EPON-ONU-INTERFACE
		    TruthValue,RowStatus,PhysAddress,DisplayString,MacAddress
		    	FROM SNMPv2-TC
		    Counter64
		        FROM SNMPv2-SMI;
                      
               
               bdepononuifStatsTable OBJECT-TYPE
                   SYNTAX  SEQUENCE OF BdEponOnuIfStatsEntry
                   ACCESS  not-accessible
                   STATUS  mandatory
                   DESCRIPTION
                            "A list of epon ONU port property value statistics table entries."
                   ::= { bdEponOnuIf 2 }

               bdEponOnuIfStatsEntry OBJECT-TYPE
                   SYNTAX  BdEponOnuIfStatsEntry
                   ACCESS  not-accessible
                   STATUS  mandatory
                   DESCRIPTION
                            "A collection of additional objects in the
                            epon ONU port property value statistics table."
                   INDEX { onuLlidDiid,onuIfSequenceNo }
               ::= { bdepononuifStatsTable 1 }

               BdEponOnuIfStatsEntry ::=
                   SEQUENCE {
                       onuLlidDiid
                           INTEGER,
                       onuIfSequenceNo
                           INTEGER,
                       ifInGoodOctets
                           Counter64,
                       ifInBadOctets
                           Counter64,
                       ifInBroadcasts
                           Counter64,
                       ifInMulticasts
                           Counter64,
                       ifInUnicasts
                           Counter64,
                       ifInPause
                           Counter64,
                       ifInMACRcvErr
                           Counter64,
                       ifInFCSErr
                           Counter64,
                       ifUndersize
                           Counter64,
                       ifFragments
                           Counter64,
                       ifOversize 
                           Counter64,
                       ifJabber
                           Counter64,
                       ifOutOctets
                           Counter64,
                       ifOutBroadcasts
                           Counter64,
                       ifOutMulticasts
                           Counter64,
                       ifOutUnicasts
                           Counter64,
                       ifOutPause
                           Counter64,
                       ifOutFCSErr
                           Counter64,
                       ifDeferred
                           Counter64,
                       ifExcessive
                           Counter64,
                       ifSingle
                           Counter64,
                       ifMultiple
                           Counter64,
                       ifLate
                           Counter64,
                       ifCollisions
                           Counter64,
                       ifPkts64Octets
                           Counter64,
                       ifPkts127Octets
                           Counter64,
                       ifPkts255Octets
                           Counter64,
                       ifPkts511Octets
                           Counter64,
                       ifPkts1023Octets
                           Counter64,
                       ifMaxOctets
                           Counter64

               }
               
               onuLlidDiid OBJECT-TYPE
                   SYNTAX  INTEGER
                   ACCESS  read-only
                   STATUS  mandatory
                   DESCRIPTION
                           "LLID port DIID, as one of the index together with onuIfSequenceNo."
                   ::= { bdEponOnuIfStatsEntry 1 } 

               onuIfSequenceNo OBJECT-TYPE
                   SYNTAX  INTEGER
                   ACCESS  read-only
                   STATUS  mandatory
                   DESCRIPTION
                           "ONU interface sequence number, as one of the index together with onuLlidDiid."
                   ::= { bdEponOnuIfStatsEntry 2 } 
               
               ifInGoodOctets OBJECT-TYPE
                   SYNTAX  Counter64
                   ACCESS  read-only
                   STATUS  mandatory
                   DESCRIPTION
                           "The total number of good octets received on the UNI interface."
                   ::= { bdEponOnuIfStatsEntry 3 } 

               ifInBadOctets OBJECT-TYPE
                   SYNTAX  Counter64
                   ACCESS  read-only
                   STATUS  mandatory
                   DESCRIPTION
                           "The total number of bad octets received on the UNI interface."
                   ::= { bdEponOnuIfStatsEntry 4 } 
               
               ifInBroadcasts OBJECT-TYPE
                   SYNTAX  Counter64
                   ACCESS  read-only
                   STATUS  mandatory
                   DESCRIPTION
                           "The total number of broadcast packages received on the UNI interface."
                   ::= { bdEponOnuIfStatsEntry 5 } 
               
               ifInMulticasts OBJECT-TYPE
                   SYNTAX  Counter64
                   ACCESS  read-only
                   STATUS  mandatory
                   DESCRIPTION
                           "The total number of multicast packages received on the UNI interface."
                   ::= { bdEponOnuIfStatsEntry 6 } 
               
               ifInUnicasts OBJECT-TYPE
                   SYNTAX  Counter64
                   ACCESS  read-only
                   STATUS  mandatory
                   DESCRIPTION
                           "The total number of unicast packages received on the UNI interface."
                   ::= { bdEponOnuIfStatsEntry 7 } 
               
               ifInPause OBJECT-TYPE
                   SYNTAX  Counter64
                   ACCESS  read-only
                   STATUS  mandatory
                   DESCRIPTION
                           "The total number of pause frames received on the UNI interface."
                   ::= { bdEponOnuIfStatsEntry 8 } 
               
               ifInMACRcvErr OBJECT-TYPE
                   SYNTAX  Counter64
                   ACCESS  read-only
                   STATUS  mandatory
                   DESCRIPTION
                           "The total number of MAC error frames received on the UNI interface."
                   ::= { bdEponOnuIfStatsEntry 9 } 
               
               ifInFCSErr OBJECT-TYPE
                   SYNTAX  Counter64
                   ACCESS  read-only
                   STATUS  mandatory
                   DESCRIPTION
                           "The total number of FCS error frames received on the UNI interface."
                   ::= { bdEponOnuIfStatsEntry 10 } 
               
               ifUndersize OBJECT-TYPE
                   SYNTAX  Counter64
                   ACCESS  read-only
                   STATUS  mandatory
                   DESCRIPTION
                           "The total number of good FCS frames under 64 octets received on the UNI interface."
                   ::= { bdEponOnuIfStatsEntry 11 } 
               
               ifFragments OBJECT-TYPE
                   SYNTAX  Counter64
                   ACCESS  read-only
                   STATUS  mandatory
                   DESCRIPTION
                           "The total number of bad FCS frames under 64 octets received on the UNI interface."
                   ::= { bdEponOnuIfStatsEntry 12 } 
               
               ifOversize OBJECT-TYPE
                   SYNTAX  Counter64
                   ACCESS  read-only
                   STATUS  mandatory
                   DESCRIPTION
                           "The total number of good FCS oversize frames received on the UNI interface."
                   ::= { bdEponOnuIfStatsEntry 13 } 
               
               ifJabber OBJECT-TYPE
                   SYNTAX  Counter64
                   ACCESS  read-only
                   STATUS  mandatory
                   DESCRIPTION
                           "The total number of bad FCS oversize frames received on the UNI interface."
                   ::= { bdEponOnuIfStatsEntry 14 } 
               
               ifOutOctets OBJECT-TYPE
                   SYNTAX  Counter64
                   ACCESS  read-only
                   STATUS  mandatory
                   DESCRIPTION
                           "The total number of octets transmitted out of the UNI interface."
                   ::= { bdEponOnuIfStatsEntry 15 } 
               
               ifOutBroadcasts OBJECT-TYPE
                   SYNTAX  Counter64
                   ACCESS  read-only
                   STATUS  mandatory
                   DESCRIPTION
                           "The total number of broadcast packages transmitted out of the UNI interface."
                   ::= { bdEponOnuIfStatsEntry 16 } 
               
               ifOutMulticasts OBJECT-TYPE
                   SYNTAX  Counter64
                   ACCESS  read-only
                   STATUS  mandatory
                   DESCRIPTION
                           "The total number of multicast packages transmitted out of the UNI interface."
                   ::= { bdEponOnuIfStatsEntry 17 } 
               
               ifOutUnicasts OBJECT-TYPE
                   SYNTAX  Counter64
                   ACCESS  read-only
                   STATUS  mandatory
                   DESCRIPTION
                           "The total number of unicast packages transmitted out of the UNI interface."
                   ::= { bdEponOnuIfStatsEntry 18 } 
               
               ifOutPause OBJECT-TYPE
                   SYNTAX  Counter64
                   ACCESS  read-only
                   STATUS  mandatory
                   DESCRIPTION
                           "The total number of Pause frames transmitted out of the UNI interface."
                   ::= { bdEponOnuIfStatsEntry 19 } 
               
               ifOutFCSErr OBJECT-TYPE
                   SYNTAX  Counter64
                   ACCESS  read-only
                   STATUS  mandatory
                   DESCRIPTION
                           "The total number of error FCS frames transmitted out of the UNI interface."
                   ::= { bdEponOnuIfStatsEntry 20 } 
               
               ifDeferred OBJECT-TYPE
                   SYNTAX  Counter64
                   ACCESS  read-only
                   STATUS  mandatory
                   DESCRIPTION
                           "For CSMA/CD, the total number of deferred frames transmitted out of the UNI interface in half duplex."
                   ::= { bdEponOnuIfStatsEntry 21 } 
               
               ifExcessive OBJECT-TYPE
                   SYNTAX  Counter64
                   ACCESS  read-only
                   STATUS  mandatory
                   DESCRIPTION
                           "For CSMA/CD, the total number of frames discarded on the UNI interface in half duplex."
                   ::= { bdEponOnuIfStatsEntry 22 } 
               
               ifSingle OBJECT-TYPE
                   SYNTAX  Counter64
                   ACCESS  read-only
                   STATUS  mandatory
                   DESCRIPTION
                           "For CSMA/CD, the total number of frames transmitted out of the UNI interface through single collision in half duplex."
                   ::= { bdEponOnuIfStatsEntry 23 } 
               
               ifMultiple OBJECT-TYPE
                   SYNTAX  Counter64
                   ACCESS  read-only
                   STATUS  mandatory
                   DESCRIPTION
                           "For CSMA/CD, the total number of frames transmitted out of the UNI interface through multiple collisions in half duplex."
                   ::= { bdEponOnuIfStatsEntry 24 } 
               
               ifLate OBJECT-TYPE
                   SYNTAX  Counter64
                   ACCESS  read-only
                   STATUS  mandatory
                   DESCRIPTION
                           "For CSMA/CD, the total number of collision frames late for 512bits-times transmitted out of the UNI interface in half duplex."
                   ::= { bdEponOnuIfStatsEntry 25 } 
               
               ifCollisions OBJECT-TYPE
                   SYNTAX  Counter64
                   ACCESS  read-only
                   STATUS  mandatory
                   DESCRIPTION
                           "The total number of collision events on the UNI interface, excluding Deferred, Excessive, Single, Multiple, and Late. "
                   ::= { bdEponOnuIfStatsEntry 26 } 
               
               ifPkts64Octets OBJECT-TYPE
                   SYNTAX  Counter64
                   ACCESS  read-only
                   STATUS  mandatory
                   DESCRIPTION
                           "The total number of packages received/transmitted equal to 64 octets on the UNI interface."
                   ::= { bdEponOnuIfStatsEntry 27 } 
               
               ifPkts127Octets OBJECT-TYPE
                   SYNTAX  Counter64
                   ACCESS  read-only
                   STATUS  mandatory
                   DESCRIPTION
                           "The total number of packages received/transmitted between 65 and 127 octets on the UNI interface."
                   ::= { bdEponOnuIfStatsEntry 28 } 
               
               ifPkts255Octets OBJECT-TYPE
                   SYNTAX  Counter64
                   ACCESS  read-only
                   STATUS  mandatory
                   DESCRIPTION
                           "The total number of packages received/transmitted between 128 and 255 octets on the UNI interface."
                   ::= { bdEponOnuIfStatsEntry 29 } 
               
               ifPkts511Octets OBJECT-TYPE
                   SYNTAX  Counter64
                   ACCESS  read-only
                   STATUS  mandatory
                   DESCRIPTION
                           "The total number of packages received/transmitted between 256 and 511 octets on the UNI interface."
                   ::= { bdEponOnuIfStatsEntry 30 } 
               
               ifPkts1023Octets OBJECT-TYPE
                   SYNTAX  Counter64
                   ACCESS  read-only
                   STATUS  mandatory
                   DESCRIPTION
                           "The total number of packages received/transmitted between 512 and 1023 octets on the UNI interface."
                   ::= { bdEponOnuIfStatsEntry 31 } 
               
               ifMaxOctets OBJECT-TYPE
                   SYNTAX  Counter64
                   ACCESS  read-only
                   STATUS  mandatory
                   DESCRIPTION
                           "The total number of packages received/transmitted between 1024 and maximal octets on the UNI interface."
                   ::= { bdEponOnuIfStatsEntry 32 } 

END
