-- *****************************************************************
-- BDCOM-EPON-OLT-NNI.MIB:  BDCom OLT-NNI MIB file
-- AUG 2009
-- *****************************************************************
--

               BDCOM-EPON-OLT-NNI DEFINITIONS ::= BEGIN

               IMPORTS
                    Counter, IpAddress, Counter
			FROM RFC1155-SMI
		    OBJECT-TYPE
			FROM RFC-1212
                    DisplayString, ifIndex, PhysAddress, TimeTicks
			FROM RFC1213-MIB
		    bdEPONGroup
			FROM BDCOM-SMI;
          
               bdEponOltNni         OBJECT IDENTIFIER ::= { bdEPONGroup 8 }

               bdeponoltnniTable OBJECT-TYPE
                   SYNTAX  SEQUENCE OF BdEponOltNniEntry
                   ACCESS  not-accessible
                   STATUS  mandatory
                   DESCRIPTION
                            "A list of epon olt NNI interface table entries."
                   ::= { bdEponOltNni 1 }

               bdEponOltNniEntry OBJECT-TYPE
                   SYNTAX BdEponOltNniEntry
                   ACCESS  not-accessible
                   STATUS  mandatory
                   DESCRIPTION
                            "A collection of additional objects in the
                            epon olt NNI table."
                   INDEX { nniIfIndex }
               ::= { bdeponoltnniTable 1 }

               BdEponOltNniEntry ::=
                   SEQUENCE {
                       nniIfIndex
                           INTEGER,
                       isRouter
                           INTEGER,
                       mcstQuerierExpireTime
                           TimeTicks,
                       ifDuplix
                           INTEGER
                   }



               nniIfIndex OBJECT-TYPE
                   SYNTAX  INTEGER
                   ACCESS  read-only
                   STATUS  mandatory
                   DESCRIPTION
                           "OLT NNI interface index allocated by system."
                   ::= { bdEponOltNniEntry 1 } 

               isRouter OBJECT-TYPE
                   SYNTAX  INTEGER {
                          no(0),
                          static(1),
                          dynamic(2)
                               	    }
                   ACCESS  read-write
                   STATUS  mandatory
                   DESCRIPTION
                           "If OLT NNI interface is a routing inreface or not."
                   ::= { bdEponOltNniEntry 2 } 

               mcstQuerierExpireTime OBJECT-TYPE
                   SYNTAX  TimeTicks
                   ACCESS  read-only
                   STATUS  mandatory
                   DESCRIPTION
                           "OLT NNI interface MCST querier expire time."
                   ::= { bdEponOltNniEntry 3 } 

               ifDuplix OBJECT-TYPE
                   SYNTAX  INTEGER{
                                   auto(0),
                                   full(1),
                                   half(2)
                                  }
                   ACCESS  read-write
                   STATUS  mandatory
                   DESCRIPTION
                           "OLT NNI port duplix mode."
                   ::= { bdEponOltNniEntry 4 } 




END
