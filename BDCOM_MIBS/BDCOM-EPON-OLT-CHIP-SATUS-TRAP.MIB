-- *****************************************************************
-- BDCOM-EPON-OLT-CHIP-STATUS-TRAP.my: BDCOM EPON OLT CHIP STATUS TRAP MIB
--
-- October 2009
-- Edit by LIUQIANG
-- Copyright (c) 2009 by BDCOM, Inc.
-- All rights reserved.
-- *****************************************************************

BDCOM-EPON-OLT-CHIP-STATUS-TRAP DEFINITIONS ::= BEGIN




IMPORTS
    MODULE-IDENTITY, OBJECT-TYPE, NOTIFICATION-TYPE,INTEGER,
    Integer32, Unsigned32                       FROM SNMPv2-SMI
    MODULE-COMPLIANCE, OBJECT-GROUP,
    NOTIFICATION-GROUP                          FROM SNMPv2-CONF
    bdEPONGroup                              		FROM BDCOM-SMI
    IpAddress, TimeTicks                                   FROM RFC1155-SMI
    PhysAddress				                FROM RFC1213-MIB
    oltChipIndex, oltSlotID, oltChipModuleID, oltChipDeviceID, oltChipMACAddress, oltChipStatus       FROM BDCOM-EPON-OLT-CHIP-INFO;


               bdEponOltChipStatusTrap         OBJECT IDENTIFIER ::= { bdEPONGroup 15 }
            

-- Notifications
	bdEponOltChipStatusNotifications OBJECT IDENTIFIER
                                ::= { bdEponOltChipStatusTrap 1 }


	bdEponOltChipStatusNotification NOTIFICATION-TYPE
    		OBJECTS {
                       oltChipIndex,
                       oltSlotID,
                       oltChipModuleID,
                       oltChipDeviceID,
                       oltChipMACAddress,
                       oltChipStatus
    		}
    		STATUS      current
    		DESCRIPTION
        	"The agent generates this notification when error olt chip ."
    		::= { bdEponOltChipStatusNotifications 1 }

              

END
