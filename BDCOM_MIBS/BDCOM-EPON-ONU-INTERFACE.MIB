-- *****************************************************************
-- BDCOM-EPON-ONU-INTERFACE.MIB:  BDCom LLID ONU MIB file
-- AUG 2009
-- *****************************************************************
--

               BDCOM-EPON-ONU-INTERFACE DEFINITIONS ::= BEGIN

               IMPORTS
                    Counter, IpAddress, Counter
			FROM RFC1155-SMI
		    OBJECT-TYPE
			FROM RFC-1212
                    DisplayString
			FROM RFC1213-MIB
		    bdEPONGroup
			FROM BDCOM-SMI
		    TruthValue,RowStatus,PhysAddress,DisplayString,MacAddress
		    	FROM SNMPv2-TC;
          
               bdEponOnuIf         OBJECT IDENTIFIER ::= { bdEPONGroup 12 }
               
               
               bdepononuifTable OBJECT-TYPE
                   SYNTAX  SEQUENCE OF BdEponOnuIfEntry
                   ACCESS  not-accessible
                   STATUS  mandatory
                   DESCRIPTION
                            "A list of epon ONU port property table entries."
                   ::= { bdEponOnuIf 1 }

               bdEponOnuIfEntry OBJECT-TYPE
                   SYNTAX  BdEponOnuIfEntry
                   ACCESS  not-accessible
                   STATUS  mandatory
                   DESCRIPTION
                            "A collection of additional objects in the
                            epon ONU port property table."
                   INDEX { onuLlidDiid,onuIfSequenceNo }
               ::= { bdepononuifTable 1 }

               BdEponOnuIfEntry ::=
                   SEQUENCE {
                       onuLlidDiid
                           INTEGER,
                       onuIfSequenceNo
                           INTEGER,
                       onuPvid
                           INTEGER,
                       onuOuterTagTpid
                           INTEGER,
                       onuMcstTagStrip
                           TruthValue,
                       onuMcstMaxGroup
                           INTEGER,
                       onuUniIfAdminStatus
                           TruthValue,
                       onuUniIfOperStatus
                           TruthValue,
                       onuUniIfMode
                           INTEGER,
                       onuUniIfSpeed
                           INTEGER,
                       onuUniIfFlowControlStatus
                           TruthValue,
                       onuUniIfLoopbackTest
                           TruthValue,
                       onuUniIfSpeedLimit
                           INTEGER,
                       onuUniIfStormControlType
                           INTEGER,
                       onuUniIfStormControlThreshold
                           INTEGER,
                       onuUniIfStormControlRowStatus
                           RowStatus,
                       onuUniIfDynamicMacLearningLimit
                           INTEGER,
                       onuUniIfVlanMode
                           INTEGER,
                       onuUniIfVlanCost
                           INTEGER
		}	             

               onuLlidDiid OBJECT-TYPE
                   SYNTAX  INTEGER
                   ACCESS  read-only
                   STATUS  mandatory
                   DESCRIPTION
                           "LLID port DIID, as one of the index together with onuIfSequenceNo."
                   ::= { bdEponOnuIfEntry 1 } 

               onuIfSequenceNo OBJECT-TYPE
                   SYNTAX  INTEGER
                   ACCESS  read-only
                   STATUS  mandatory
                   DESCRIPTION
                           "ONU interface sequence number, as one of the index together with onuLlidDiid."
                   ::= { bdEponOnuIfEntry 2 } 
		
               onuPvid OBJECT-TYPE
                   SYNTAX  INTEGER(1..4094)
                   ACCESS  read-write
                   STATUS  mandatory
                   DESCRIPTION
                           "ONU PVID, range is 1 to 4094. Only UNI set is supported."
                   ::= { bdEponOnuIfEntry 3 } 
		
               onuOuterTagTpid OBJECT-TYPE
                   SYNTAX  INTEGER
                   ACCESS  read-write
                   STATUS  mandatory
                   DESCRIPTION
                           "The TPID value of the outer tag. Only UNI set is supported."
                   ::= { bdEponOnuIfEntry 4 } 
		
               onuMcstTagStrip OBJECT-TYPE
                   SYNTAX  TruthValue
                   ACCESS  read-write
                   STATUS  mandatory
                   DESCRIPTION
                           "if onuMcstTagStrip is TRUE, ONU will stripe VLAN tag of in downstream, 
                           and if onuMcstTagStrip is FALSE, ONU will not stripe VLAN tag of in downstream."
                   ::= { bdEponOnuIfEntry 5 } 
		
               onuMcstMaxGroup OBJECT-TYPE
                   SYNTAX  INTEGER(1..64)
                   ACCESS  read-write
                   STATUS  mandatory
                   DESCRIPTION
                           "The maximum group number which an UNI port can hold. This value can be set only in igmp-snooping mode."
                   ::= { bdEponOnuIfEntry 6 } 
		
               onuUniIfAdminStatus OBJECT-TYPE
                   SYNTAX  TruthValue
                   ACCESS  read-write
                   STATUS  mandatory
                   DESCRIPTION
                           "ONU UNI port administration status."
                   ::= { bdEponOnuIfEntry 7 } 
		
               onuUniIfOperStatus OBJECT-TYPE
                   SYNTAX  TruthValue
                   ACCESS  read-write
                   STATUS  mandatory
                   DESCRIPTION
                           "ONU UNI port operating status."
                   ::= { bdEponOnuIfEntry 8 } 
		
               onuUniIfMode OBJECT-TYPE
                   SYNTAX  INTEGER{
                          full(1),
                          half(2),
                          auto(3)
                   }
                   ACCESS  read-write
                   STATUS  mandatory
                   DESCRIPTION
                           "ONU UNI port mode(1-full，2-half，3-auto)."
                   ::= { bdEponOnuIfEntry 9 } 
		
               onuUniIfSpeed OBJECT-TYPE
                   SYNTAX  INTEGER{
                          s10M(1),
                          s100M(2),
                          s1000M(3),
                          auto(4)
                   }
                   ACCESS  read-write
                   STATUS  mandatory
                   DESCRIPTION
                           "ONU UNI port speed(1-10M，2-100M，3-1000M(ONU not support currently)4-auto)."
                   ::= { bdEponOnuIfEntry 10 } 
		
               onuUniIfFlowControlStatus OBJECT-TYPE
                   SYNTAX  TruthValue
                   ACCESS  read-write
                   STATUS  mandatory
                   DESCRIPTION
                           "ONU UNI port flow control status."
                   ::= { bdEponOnuIfEntry 11 } 
		
               onuUniIfLoopbackTest OBJECT-TYPE
                   SYNTAX  TruthValue
                   ACCESS  read-write
                   STATUS  mandatory
                   DESCRIPTION
                           "ONU UNI port loopback test."
                   ::= { bdEponOnuIfEntry 12 } 
		
               onuUniIfSpeedLimit OBJECT-TYPE
                   SYNTAX  INTEGER(64..100000)
                   ACCESS  read-write
                   STATUS  mandatory
                   DESCRIPTION
                           "ONU UNI port speed limit()."
                   ::= { bdEponOnuIfEntry 13 } 
		
               onuUniIfStormControlType OBJECT-TYPE
                   SYNTAX  INTEGER{
                          broadcast(1),
                          broadcast-multicast(2),
                          broadcast-multicast-unkown-unicast(3)
                   }
                   ACCESS  read-write
                   STATUS  mandatory
                   DESCRIPTION
                           "ONU UNI port storm control type(broadcast(1),broadcast-multicast(2),broadcast-multicast-unkown-unicast(3)."
                   ::= { bdEponOnuIfEntry 14 } 
		
               onuUniIfStormControlThreshold OBJECT-TYPE
                   SYNTAX  INTEGER(256..100000)
                   ACCESS  read-write
                   STATUS  mandatory
                   DESCRIPTION
                           "ONU UNI port storm control threshold(256~100000kbps)."
                   ::= { bdEponOnuIfEntry 15 } 
		
               onuUniIfStormControlRowStatus OBJECT-TYPE
                   SYNTAX  RowStatus
                   ACCESS  read-create
                   STATUS  mandatory
                   DESCRIPTION
                           "ONU UNI port storm control configuration row status."
                   ::= { bdEponOnuIfEntry 16 } 
		
               onuUniIfDynamicMacLearningLimit OBJECT-TYPE
                   SYNTAX  INTEGER(1..63)
                   ACCESS  read-write
                   STATUS  mandatory
                   DESCRIPTION
                           "ONU UNI port dynamic MAC address learning number limitation(1~63)."
                   ::= { bdEponOnuIfEntry 17 } 

               onuUniIfVlanMode OBJECT-TYPE
                   SYNTAX  INTEGER{
                                   transparent-mode(0),
                                   tag-mode(1),
                                   translation-mode(2),
                                   stacking-mode(3),
                                   none(4)
                                  }
                   ACCESS  read-write
                   STATUS  mandatory
                   DESCRIPTION
                           "ONU UNI port VLAN mode."
                   ::= { bdEponOnuIfEntry 18 } 

               onuUniIfVlanCost OBJECT-TYPE
                   SYNTAX  INTEGER(0..7)
                   ACCESS  read-write
                   STATUS  mandatory
                   DESCRIPTION
                           "ONU UNI port VLAN cost. Default value is 0."
                   ::= { bdEponOnuIfEntry 19 } 


END
